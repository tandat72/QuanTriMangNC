ProxyCache-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        proxyServer     OBJECT IDENTIFIER ::= { internetServer 11 }
        cacheStatistics OBJECT IDENTIFIER ::= { proxyServer 2 }

-- Proxy Cache Statistics
	UrlsInCache OBJECT-TYPE
		SYNTAX	Integer
		ACCESS	read-only
		STATUS	mandatory
		DESCRIPTION 
			"The current number of URLs stored in the cache."
		::= { cacheStatistics 1 }

	TotalMemoryBytesRetrieved OBJECT-TYPE
		SYNTAX	Counter
		ACCESS	read-only
		STATUS	mandatory
		DESCRIPTION 
			"The cumulative number of kilobytes retrieved from the memory cache."
		::= { cacheStatistics 2 }

	TotalDiskBytesRetrieved OBJECT-TYPE
		SYNTAX	Counter
		ACCESS	read-only
		STATUS	mandatory
		DESCRIPTION 
			"The cumulative number of kilobytes retrieved from the disk cache."
		::= { cacheStatistics 3 }

	TotalUrlsCached OBJECT-TYPE
		SYNTAX	Counter
		ACCESS	read-only
		STATUS	mandatory
		DESCRIPTION 
			"The cumulative number of URLs stored in the cache."
		::= { cacheStatistics 4 }

	TotalMemoryUrlsRetrieved OBJECT-TYPE
		SYNTAX	Counter
		ACCESS	read-only
		STATUS	mandatory
		DESCRIPTION 
			"The cumulative number of URLs retrieved from the memory cache."
		::= { cacheStatistics 5 }

	TotalDiskUrlsRetrieved OBJECT-TYPE
		SYNTAX	Counter
		ACCESS	read-only
		STATUS	mandatory
		DESCRIPTION 
			"The cumulative number of URLs retrieved from the disk cache."
		::= { cacheStatistics 6 }

	MaxUrlsCached OBJECT-TYPE
		SYNTAX	Counter
		ACCESS	read-only
		STATUS	mandatory
		DESCRIPTION 
			"The maximum number of URLs stored in the cache simultaneously since the Firewall service was started."
		::= { cacheStatistics 7 }

	TotalDiskFailures OBJECT-TYPE
		SYNTAX	Counter
		ACCESS	read-only
		STATUS	mandatory
		DESCRIPTION 
			"The number of times since the Firewall service started that ISA Server failed to read from or write to disk cache, due to an I/O failure."
		::= { cacheStatistics 8 }

	DiskFailuresRate OBJECT-TYPE
		SYNTAX	Counter
		ACCESS	read-only
		STATUS	mandatory
		DESCRIPTION 
			"The number of I/O failures per second since the Firewall service started. An I/O failure occurs when ISA Server fails to read from or write to disk cache."
		::= { cacheStatistics 9 }

	MemoryCacheAllocatedSpace OBJECT-TYPE
		SYNTAX	Counter
		ACCESS	read-only
		STATUS	mandatory
		DESCRIPTION 
			"The amount of space used for the memory cache (from the total memory allocated for memory caching)."
		::= { cacheStatistics 10 }

	DiskCacheAllocatedSpaceSum OBJECT-TYPE
		SYNTAX	Counter
		ACCESS	read-only
		STATUS	mandatory
		DESCRIPTION 
			"The amount of space used for the disk cache (from the total disk space allocated for disk caching)."
		::= { cacheStatistics 11 }

	MemoryUsageRatioPercent OBJECT-TYPE
		SYNTAX	Counter
		ACCESS	read-only
		STATUS	mandatory
		DESCRIPTION 
			"The amount of fetches from the memory cache, in proportion to the total fetches from the cache."
		::= { cacheStatistics 12 }

	ContentDiskWritesRate OBJECT-TYPE
		SYNTAX	Counter
		ACCESS	read-only
		STATUS	mandatory
		DESCRIPTION 
			"The amount of writes to the disk cache, per second."
		::= { cacheStatistics 13 }

	MemoryRetrieves OBJECT-TYPE
		SYNTAX	Counter
		ACCESS	read-only
		STATUS	mandatory
		DESCRIPTION 
			"The rate at which URLs are retrieved from the memory cache."
		::= { cacheStatistics 14 }

	DiskRetrieves OBJECT-TYPE
		SYNTAX	Counter
		ACCESS	read-only
		STATUS	mandatory
		DESCRIPTION 
			"The rate at which URLs are retrieved from the disk cache."
		::= { cacheStatistics 15 }

	MemoryRetrieveBytes OBJECT-TYPE
		SYNTAX	Counter
		ACCESS	read-only
		STATUS	mandatory
		DESCRIPTION 
			"The rate at which kilobytes of data are retrieved from the memory cache."
		::= { cacheStatistics 16 }

	DiskRetrieveBytes OBJECT-TYPE
		SYNTAX	Counter
		ACCESS	read-only
		STATUS	mandatory
		DESCRIPTION 
			"The rate at which kilobytes of data are retrieved from the disk cache."
		::= { cacheStatistics 17 }

	Commits OBJECT-TYPE
		SYNTAX	Counter
		ACCESS	read-only
		STATUS	mandatory
		DESCRIPTION 
			"The rate at which URLs are stored to the cache."
		::= { cacheStatistics 18 }


END
