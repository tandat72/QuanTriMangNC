WspServer-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        WspServer       OBJECT IDENTIFIER ::= { internetServer 12 }
        WspStatistics   OBJECT IDENTIFIER ::= { WspServer 1 }

-- WinSock Proxy Server Statistics
	ActiveSessions OBJECT-TYPE
		SYNTAX	Integer
		ACCESS	read-only
		STATUS	mandatory
		DESCRIPTION 
			"The number of active Firewall Service sessions."
		::= { WspStatistics 1 }

	ActiveTCPConnections OBJECT-TYPE
		SYNTAX	Integer
		ACCESS	read-only
		STATUS	mandatory
		DESCRIPTION 
			"The total number of active TCP connections currently passing data. Connections pending or not yet established are counted elsewhere."
		::= { WspStatistics 2 }

	ActiveUDPConnections OBJECT-TYPE
		SYNTAX	Integer
		ACCESS	read-only
		STATUS	mandatory
		DESCRIPTION 
			"The total number of active UDP connections."
		::= { WspStatistics 3 }

	ConnectingTCPConnections OBJECT-TYPE
		SYNTAX	Integer
		ACCESS	read-only
		STATUS	mandatory
		DESCRIPTION 
			"The total number of pending TCP connections. This is the total number of connections that are waiting for a connect call to finish."
		::= { WspStatistics 4 }

	BackConnectingTCPConnections OBJECT-TYPE
		SYNTAX	Integer
		ACCESS	read-only
		STATUS	mandatory
		DESCRIPTION 
			"The total number of TCP connections awaiting an inbound connect call to finish. These are connections from the Firewall Service to a Firewall client after the Firewall Service accepted a connection from the Internet on a listening socket."
		::= { WspStatistics 5 }

	AcceptingTCPConnections OBJECT-TYPE
		SYNTAX	Integer
		ACCESS	read-only
		STATUS	mandatory
		DESCRIPTION 
			"The number of connection objects waiting for a TCP connection from the Firewall client after a successful remote connection."
		::= { WspStatistics 6 }

	ListeningTCPConnections OBJECT-TYPE
		SYNTAX	Integer
		ACCESS	read-only
		STATUS	mandatory
		DESCRIPTION 
			"The number of connection objects waiting for TCP connections from remote computers (after a successful listen)."
		::= { WspStatistics 7 }

	AllocFailureLogs OBJECT-TYPE
		SYNTAX	Counter
		ACCESS	read-only
		STATUS	mandatory
		DESCRIPTION 
			"The number of memory allocation errors."
		::= { WspStatistics 8 }

	PumpTotalRead OBJECT-TYPE
		SYNTAX	Counter
		ACCESS	read-only
		STATUS	mandatory
		DESCRIPTION 
			"The number of bytes read by the data-pump per second."
		::= { WspStatistics 9 }

	PumpTotalWrite OBJECT-TYPE
		SYNTAX	Counter
		ACCESS	read-only
		STATUS	mandatory
		DESCRIPTION 
			"Number of bytes written by data-pump per second."
		::= { WspStatistics 10 }

	PendingGetXByY OBJECT-TYPE
		SYNTAX	Counter
		ACCESS	read-only
		STATUS	mandatory
		DESCRIPTION 
			"Number of gethostbyname and gethostbyaddr API calls pending resolution. These are calls used to resolve host DNS domain names and IP addresses for Firewall Service connections."
		::= { WspStatistics 11 }

	SuccessGetXByY OBJECT-TYPE
		SYNTAX	Counter
		ACCESS	read-only
		STATUS	mandatory
		DESCRIPTION 
			"Number of gethostbyname and gethostbyaddr API calls successfully returned. These are calls used to resolve host DNS domain names and IP addresses for Firewall Service connections."
		::= { WspStatistics 12 }

	FailedGetXByY OBJECT-TYPE
		SYNTAX	Counter
		ACCESS	read-only
		STATUS	mandatory
		DESCRIPTION 
			"Number of gethostbyname and gethostbyaddr API calls that have failed. These are calls used to resolve host DNS domain names and IP addresses for Firewall Service connections."
		::= { WspStatistics 13 }

	CtrlWorkerThreads OBJECT-TYPE
		SYNTAX	Counter
		ACCESS	read-only
		STATUS	mandatory
		DESCRIPTION 
			"The number of Firewall Service worker threads that are currently alive."
		::= { WspStatistics 14 }

	CtrlAvailableWorkerThreads OBJECT-TYPE
		SYNTAX	Integer
		ACCESS	read-only
		STATUS	mandatory
		DESCRIPTION 
			"The number of Firewall Service worker threads that are available (waiting in completion port queue)."
		::= { WspStatistics 15 }

	Mappings OBJECT-TYPE
		SYNTAX	Integer
		ACCESS	read-only
		STATUS	mandatory
		DESCRIPTION 
			"The number of mappings available for UDP connections."
		::= { WspStatistics 16 }

	PNATMappings OBJECT-TYPE
		SYNTAX	Integer
		ACCESS	read-only
		STATUS	mandatory
		DESCRIPTION 
			"The number of mappings created by SecureNAT."
		::= { WspStatistics 17 }

	KernelDataPumps OBJECT-TYPE
		SYNTAX	Integer
		ACCESS	read-only
		STATUS	mandatory
		DESCRIPTION 
			"The number of kernel mode data pumps created by the Firewall Service."
		::= { WspStatistics 18 }

	KernelTotalTCPBytes OBJECT-TYPE
		SYNTAX	Counter
		ACCESS	read-only
		STATUS	mandatory
		DESCRIPTION 
			"The number of TCP bytes transferred by the kernel mode data-pump per second."
		::= { WspStatistics 19 }

	KernelTotalUDPBytes OBJECT-TYPE
		SYNTAX	Counter
		ACCESS	read-only
		STATUS	mandatory
		DESCRIPTION 
			"Number of UDP bytes transferred by the kernel mode data-pump per second."
		::= { WspStatistics 20 }

	DnsCacheEntries OBJECT-TYPE
		SYNTAX	Counter
		ACCESS	read-only
		STATUS	mandatory
		DESCRIPTION 
			"The number of DNS domain name entries cached by the Firewall Service."
		::= { WspStatistics 21 }

	DnsCacheHits OBJECT-TYPE
		SYNTAX	Counter
		ACCESS	read-only
		STATUS	mandatory
		DESCRIPTION 
			"The total number of times a DNS domain name was found in the DNS Cache."
		::= { WspStatistics 22 }

	DnsCacheFlushes OBJECT-TYPE
		SYNTAX	Counter
		ACCESS	read-only
		STATUS	mandatory
		DESCRIPTION 
			"The total number of times that the DNS domain name cache has been flushed or cleared by ISA Server."
		::= { WspStatistics 23 }

	DnsCacheRetrievals OBJECT-TYPE
		SYNTAX	Counter
		ACCESS	read-only
		STATUS	mandatory
		DESCRIPTION 
			"The total number of DNS domain names retrieved by the Firewall Service."
		::= { WspStatistics 24 }

	DnsCacheRatio OBJECT-TYPE
		SYNTAX	Integer
		ACCESS	read-only
		STATUS	mandatory
		DESCRIPTION 
			"The percentage of DNS domain names retrieved from the DNS cache, out of a total of all DNS entries retrieved from the Firewall Service."
		::= { WspStatistics 25 }

	VpnClientSessions OBJECT-TYPE
		SYNTAX	Integer
		ACCESS	read-only
		STATUS	mandatory
		DESCRIPTION 
			"The number of VPN client sessions."
		::= { WspStatistics 26 }

	VpnClientSessionsSecond OBJECT-TYPE
		SYNTAX	Integer
		ACCESS	read-only
		STATUS	mandatory
		DESCRIPTION 
			"The number of VPN client sessions per second."
		::= { WspStatistics 27 }

	FwLogFlushRetries OBJECT-TYPE
		SYNTAX	Integer
		ACCESS	read-only
		STATUS	mandatory
		DESCRIPTION 
			"The number of FW log retries."
		::= { WspStatistics 28 }

	WebLogFlushRetries OBJECT-TYPE
		SYNTAX	Integer
		ACCESS	read-only
		STATUS	mandatory
		DESCRIPTION 
			"The number of web log retries."
		::= { WspStatistics 29 }

	FwLogEntriesSecond OBJECT-TYPE
		SYNTAX	Integer
		ACCESS	read-only
		STATUS	mandatory
		DESCRIPTION 
			"The number of FW log entires per second."
		::= { WspStatistics 30 }

	WebLogEntriesSecond OBJECT-TYPE
		SYNTAX	Integer
		ACCESS	read-only
		STATUS	mandatory
		DESCRIPTION 
			"The number of web log entires per second."
		::= { WspStatistics 31 }

	FwRowsFlashedInCurrentBatch OBJECT-TYPE
		SYNTAX	Integer
		ACCESS	read-only
		STATUS	mandatory
		DESCRIPTION 
			"The number of FW rows flushed in current batch."
		::= { WspStatistics 32 }

	WebRowsFlashedInCurrentBatch OBJECT-TYPE
		SYNTAX	Integer
		ACCESS	read-only
		STATUS	mandatory
		DESCRIPTION 
			"The number of web rows flushed in current batch."
		::= { WspStatistics 33 }

	KernelConnections OBJECT-TYPE
		SYNTAX	Integer
		ACCESS	read-only
		STATUS	mandatory
		DESCRIPTION 
			"The total number of active kernel connections."
		::= { WspStatistics 34 }

	KernelConnectionsSecond OBJECT-TYPE
		SYNTAX	Integer
		ACCESS	read-only
		STATUS	mandatory
		DESCRIPTION 
			"The total number of active kernel connections per second."
		::= { WspStatistics 35 }

	RawConnections OBJECT-TYPE
		SYNTAX	Integer
		ACCESS	read-only
		STATUS	mandatory
		DESCRIPTION 
			"The total number of raw kernel connections."
		::= { WspStatistics 36 }

	RawConnectionsSecond OBJECT-TYPE
		SYNTAX	Integer
		ACCESS	read-only
		STATUS	mandatory
		DESCRIPTION 
			"The total number of raw kernel connections per second."
		::= { WspStatistics 37 }

	FailedFWCConnect OBJECT-TYPE
		SYNTAX	Integer
		ACCESS	read-only
		STATUS	mandatory
		DESCRIPTION 
			"The total number of FWC connections attempts which failed."
		::= { WspStatistics 38 }

	FailedFWCConnectSecond OBJECT-TYPE
		SYNTAX	Integer
		ACCESS	read-only
		STATUS	mandatory
		DESCRIPTION 
			"The total number of FWC connections attempts which failed per second."
		::= { WspStatistics 39 }

	FailedReinjectConnect OBJECT-TYPE
		SYNTAX	Integer
		ACCESS	read-only
		STATUS	mandatory
		DESCRIPTION 
			"The total number of Reinjected connections attempts which failed."
		::= { WspStatistics 40 }

	FailedReinjectConnectSecond OBJECT-TYPE
		SYNTAX	Integer
		ACCESS	read-only
		STATUS	mandatory
		DESCRIPTION 
			"The total number of Reinjected connections attempts which failed per second."
		::= { WspStatistics 41 }

	TimedoutConnections OBJECT-TYPE
		SYNTAX	Integer
		ACCESS	read-only
		STATUS	mandatory
		DESCRIPTION 
			"The total number of TCP connections which were timed out."
		::= { WspStatistics 42 }

	TimedoutConnectionsSecond OBJECT-TYPE
		SYNTAX	Integer
		ACCESS	read-only
		STATUS	mandatory
		DESCRIPTION 
			"The total number of TCP connections which were timed out per second."
		::= { WspStatistics 43 }

	EventActions OBJECT-TYPE
		SYNTAX	Integer
		ACCESS	read-only
		STATUS	mandatory
		DESCRIPTION 
			"The total number of event actions."
		::= { WspStatistics 44 }

	EventActionsSecond OBJECT-TYPE
		SYNTAX	Integer
		ACCESS	read-only
		STATUS	mandatory
		DESCRIPTION 
			"The total number of event actions per second."
		::= { WspStatistics 45 }

	ClosedQuotaConnections OBJECT-TYPE
		SYNTAX	Integer
		ACCESS	read-only
		STATUS	mandatory
		DESCRIPTION 
			"The total number of connections closed by the quota."
		::= { WspStatistics 46 }

	ClosedQuotaConnectionsSecond OBJECT-TYPE
		SYNTAX	Integer
		ACCESS	read-only
		STATUS	mandatory
		DESCRIPTION 
			"The total number of connections closed by the quota per second."
		::= { WspStatistics 47 }

	OutstandingGetHostByNameCalls OBJECT-TYPE
		SYNTAX	Integer
		ACCESS	read-only
		STATUS	mandatory
		DESCRIPTION 
			"The total number of outstanding GetHostByName calls."
		::= { WspStatistics 48 }

	OutstandingGetHostByNameCallsSecond OBJECT-TYPE
		SYNTAX	Integer
		ACCESS	read-only
		STATUS	mandatory
		DESCRIPTION 
			"The total number of outstanding GetHostByName calls per second."
		::= { WspStatistics 49 }

	OutstandingForwardDnsQueryCalls OBJECT-TYPE
		SYNTAX	Integer
		ACCESS	read-only
		STATUS	mandatory
		DESCRIPTION 
			"The total number of outstanding forward DNSQuery calls"
		::= { WspStatistics 50 }

	OutstandingForwardDnsQueryCallsSecond OBJECT-TYPE
		SYNTAX	Integer
		ACCESS	read-only
		STATUS	mandatory
		DESCRIPTION 
			"The total number of outstanding forward DNSQuery calls per second."
		::= { WspStatistics 51 }

	OutstandingReverseDnsQueryCalls OBJECT-TYPE
		SYNTAX	Integer
		ACCESS	read-only
		STATUS	mandatory
		DESCRIPTION 
			"The total number of outstanding reverse DNSQuery calls"
		::= { WspStatistics 52 }

	OutstandingReverseDnsQueryCallsSecond OBJECT-TYPE
		SYNTAX	Integer
		ACCESS	read-only
		STATUS	mandatory
		DESCRIPTION 
			"The total number of outstanding reverse DNSQuery calls per second."
		::= { WspStatistics 53 }

	DnsCacheLockFails OBJECT-TYPE
		SYNTAX	Counter
		ACCESS	read-only
		STATUS	mandatory
		DESCRIPTION 
			"The total number of times that the DNS domain names cache failed locking its internal data structure."
		::= { WspStatistics 54 }

	FWLogSizeFirstBuffer OBJECT-TYPE
		SYNTAX	Integer
		ACCESS	read-only
		STATUS	mandatory
		DESCRIPTION 
			"The size of Firewall log buffer 1"
		::= { WspStatistics 55 }

	FWLogSizeSecondBuffer OBJECT-TYPE
		SYNTAX	Integer
		ACCESS	read-only
		STATUS	mandatory
		DESCRIPTION 
			"The size of Firewall log buffer 2"
		::= { WspStatistics 56 }

	ProxyLogSizeFirstBuffer OBJECT-TYPE
		SYNTAX	Integer
		ACCESS	read-only
		STATUS	mandatory
		DESCRIPTION 
			"The size of Web Proxy log buffer 1"
		::= { WspStatistics 57 }

	ProxyLogSizeSecondBuffer OBJECT-TYPE
		SYNTAX	Integer
		ACCESS	read-only
		STATUS	mandatory
		DESCRIPTION 
			"The size of Web Proxy log buffer 2"
		::= { WspStatistics 58 }


END
